;;; ====================================================================================================
;;; TNT_MIGRATE_V16_SIMPLE.lsp
;;; Run command TNT_MIGRATE_V16_SIMPLE to move old V16 layers to TNT ISO layers immediately.
;;; No preview. No report. Layers not listed here are unchanged.
;;; ====================================================================================================

(vl-load-com)

(defun TNT:V16S:MAP (/)
  '(
    ("...0_TNT_LINE_NAME"       "....01_TNT_A_DRAWING")
    ("...2_TNT_LINE_WALL"       "....17_TNT_S_WALL")
    ("2_TNT_LINE_WALL"          "....17_TNT_S_WALL")
    ("TNT-Walls"                "....17_TNT_S_WALL")
    ("TNT-Concrete"             "....16_TNT_S_CONCRETE")
    ("...3_TNT_LINE_SECTION"    "....05_TNT_A_SECTION")
    ("TNT-Net Cat"              "....05_TNT_A_SECTION")
    ("3_TNT_LINE_SECTION"       "....06_TNT_A_SECTION-LINE")
    ("...4_TNT_LINE_VIRTURAL"   "....02_TNT_A_VIRTURAL")
    ("TNT-Virtural"             "....02_TNT_A_VIRTURAL")
    ("4_TNT_LINE_VIRTURAL"      "....02_TNT_A_VIRTURAL")
    ("...5_TNT_LINE_THIN"       "....03_TNT_A_THIN")
    ("...6_TNT_LINE_HIDDEN"     "....04_TNT_A_HIDDEN")
    ("6_TNT_LINE_HIDDEN"        "....04_TNT_A_HIDDEN")
    ("TNT-Hidden N"             "....04_TNT_A_HIDDEN")
    ("...7_TNT_LINE_BASE"       "....07_TNT_A_BASE")
    ("7_TNT_LINE_BASE"          "....07_TNT_A_BASE")
    ("...8_TNT_LINE_FUNITURE"   "....12_TNT_F_FURNITURE")
    ("TNT-Funiture"             "....12_TNT_F_FURNITURE")
    ("...9_TNT_LINE_TEXT"       "....20_TNT_N_TEXT")
    ("...10_TNT_LINE_HATCH"     "....23_TNT_N_HATCH")
    ("TNT-Hatch"                "....23_TNT_N_HATCH")
    ("...11_TNT_LINE_DIMENSION" "....22_TNT_N_DIMENSION")
    ("11_TNT_LINE_DIMENSION"    "....22_TNT_N_DIMENSION")
    ("...12_TNT_LINE_ANNOTATE"  "....24_TNT_N_ANNOTATE")
    ("12_TNT_LINE_ANNOTATE"     "....24_TNT_N_ANNOTATE")
    ("...13_TNT_LINE_TREE"      "....13_TNT_F_TREE")
    ("...15_TNT_LINE_DOOR"      "....15_TNT_F_DOOR")
    ("TNT-Door"                 "....15_TNT_F_DOOR")
    ("...16_TNT_LINE_DETAIL"    "....08_TNT_A_DETAIL")
    ("16_TNT_LINE_DETAIL"       "....08_TNT_A_DETAIL")
    ("...17_TNT_SECTION_LINE"   "....06_TNT_A_SECTION-LINE")
    ("...18_TNT_N_TEXT"         "....26_TNT_M_TEXT")
    ("TNT-Text"                 "....26_TNT_M_TEXT")
    ("...19_TNT_LINE_LAYOUT"    "....11_TNT_A_PLOT")
    ("...21_TNT_LINE_COTE"      "....10_TNT_A_COTE")
  )
)

(defun TNT:V16S:LAYER-OBJ (name / doc layers result)
  (setq doc    (vla-get-ActiveDocument (vlax-get-acad-object)))
  (setq layers (vla-get-Layers doc))
  (setq result (vl-catch-all-apply 'vla-Item (list layers name)))
  (if (vl-catch-all-error-p result) nil result)
)

(defun TNT:V16S:ENSURE-LAYER (name / doc layers layerObj)
  (setq layerObj (TNT:V16S:LAYER-OBJ name))
  (if (null layerObj)
    (progn
      (setq doc    (vla-get-ActiveDocument (vlax-get-acad-object)))
      (setq layers (vla-get-Layers doc))
      (setq layerObj (vl-catch-all-apply 'vla-Add (list layers name)))
      (if (vl-catch-all-error-p layerObj)
        (setq layerObj nil)
      )
    )
  )
  layerObj
)

(defun TNT:V16S:UNLOCK (name / layerObj)
  (setq layerObj (TNT:V16S:ENSURE-LAYER name))
  (if layerObj
    (progn
      (vl-catch-all-apply 'vla-put-LayerOn (list layerObj :vlax-true))
      (vl-catch-all-apply 'vla-put-Freeze (list layerObj :vlax-false))
      (vl-catch-all-apply 'vla-put-Lock (list layerObj :vlax-false))
    )
  )
  (princ)
)

(defun TNT:V16S:MOVE (oldLayer newLayer / ss n)
  (TNT:V16S:UNLOCK oldLayer)
  (TNT:V16S:UNLOCK newLayer)
  (setq ss (ssget "_X" (list (cons 8 oldLayer))))
  (if ss
    (progn
      (setq n (sslength ss))
      (command-s "_.CHPROP" ss "" "_LA" newLayer "")
      n
    )
    0
  )
)

(defun c:TNT_MIGRATE_V16_SIMPLE (/ oldcmdecho pair total count)
  (setq oldcmdecho (getvar "CMDECHO"))
  (setvar "CMDECHO" 0)
  (command-s "_.UNDO" "_BE")
  (setq total 0)
  (foreach pair (TNT:V16S:MAP)
    (setq count (TNT:V16S:MOVE (car pair) (cadr pair)))
    (setq total (+ total count))
    (if (> count 0)
      (princ (strcat "\n[TNT] " (car pair) " -> " (cadr pair) " : " (itoa count)))
    )
  )
  (command-s "_.UNDO" "_END")
  (setvar "CMDECHO" oldcmdecho)
  (princ (strcat "\n[TNT] DONE V16 SIMPLE MIGRATE. Objects changed: " (itoa total)))
  (princ)
)

(princ "\n[TNT] Loaded TNT_MIGRATE_V16_SIMPLE.lsp. Command: TNT_MIGRATE_V16_SIMPLE")
(princ)
